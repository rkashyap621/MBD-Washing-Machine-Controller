# WMC_Ver_02_PauseFault_Requirements

## WMC-REQ-001: System Initialization (Functional)
On System start, the controller shall enter the Idle stage with all actuators OFF, cycle_complete set to 0, and fault_indicator set to 0.

## WMC-REQ-002: Start Condition (Functional)
When start_button is pressed and door_closed is 1, the controller shall start the washing cycle.

## WMC-REQ-003: Door Safety Before Start (Functional)
If start_button is pressed while door_closed is 0, the controller shall remain in Idle state and not initiate the cycle.

## WMC-REQ-004: Door Lock Activation (Functional)
After a valid start command, the controller shall activate door_lock and shall wait for door_lock_delay duration before entering the Water_Fill_Wash_Cycle stage.

## WMC-REQ-005: Wash-Cycle Water Fill (Functional)
During Water_Fill_Wash_Cycle stage, the controller shall turn ON water_valve and shall remain in this stage until water_level_ok becomes 1. The water_level_ok is shared with the rinse-cycle water fill stage.

## WMC-REQ-006: Detergent Fill Stage (Functional)
After wash-cycle water filling is completed, the controller shall enter Detergent_Fill stage and turn ON detergent_valve until detergent_level_ok becomes 1.

## WMC-REQ-007: Wash Stage (Functional)
After detergent filling is completed, the controller shall enter the Wash stage and turn on wash_motor for the configured wash_duration.

## WMC-REQ-008: Wash-Cycle Drain (Functional)
After wash_duration is completed, the controller shall enter Drain_Wash_Cycle stage and turn ON drain_pump for the configured drain_duration. The drain_duration parameter is shared with the Drain_Rinse_Cycle stage.

## WMC-REQ-009: Rinse-Cycle Water Fill (Functional)
After wash-cycle draining is completed, the controller shall enter Water_Fill_Rinse_Cycle stage and shall turn ON water_valve until water_level_ok become 1. The water_level_ok signal is shared with the wash-cycle water fill stage.

## WMC-REQ-010: Rinse Stage (Functional)
After rinse-cycle water filling is completed, the controller shall enter the Rinse stage and turn ON wash_motor for the configured rinse_duration.

## WMC-REQ-011: Rinse-Cycle Drain (Functional)
After rinse_duration is completed, the controller shall enter Drain_Rinse_Cycle stage and turn ON drain_pump for the cofigured drain_duration. The drain_duration parameter is shared with the Drain_Wash_Cycle stage.

## WMC-REQ-012: Spin Stage (Functional)
After rinse-cycle draining is completed, the controller shall enter Spin stage and turn ON the spin_motor for the configured spin_duration.

## WMC-REQ-013: Cycle Completion (Functional)
After spin_duration is completed, the controller shall enter Cycle_Complete stage, turn OFF all actuators, shall unlock the door_lock, and shall set cycle_complete to 1.

## WMC-REQ-014: Pause Command (Functional)
If pause_button is pressed during any active cycle, the controller shall enter Paused stage and turn OFF active actuator outputs.

## WMC-REQ-015: Resume Command with History (Functional)
If resume_button is pressed from the Paused stage and door_closed is 1, the controller shall resume from the previously interrupted cycle stage using Stateflow history junction behavior.

## WMC-REQ-016: Door Safety During Pause (Functional)
If door_closed is 0 during Paused stage, the controller shall not resume the cycle until door_closed becomes 1, even if resume_button is pressed.

## WMC-REQ-017: Detergent Fill Timeout Fault (Functional)
If detergent_level_ok does not become 1 within detergent_fill_timeout duration during Detergent_Fill stage, the controller shall enter Fault stage.

## WMC-REQ-018: Generic Fault Detection (Functional)
If fault_signal becomes 1 during any active cycle stage, the controller shall immediately transitition to the Fault stage.

## WMC-REQ-019: Fault Response (Functional)
In the Fault stage, the controller shall turn OFF water_valve, detergent_valve, drain_pump, wash_motor and spin_motor, and shall set fault_indicator to 1. door_lock shall remain ON in the Fault stage.

## WMC-REQ-020: Fault Reset (Functional)
If reset_button is pressed in the Fault stage and fault_signal is 0, the controller shall clear fault_indicator and with all outputs reset to Idle stage conditions.
